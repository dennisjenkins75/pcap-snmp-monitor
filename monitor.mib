-- Compile with:
-- 		MIBS="+ALL" mib2c -c mib2c.table_data.conf pcapSnmpMonitorMIB
-- Walk with:
--		snmpwalk -v2c -c public -On 127.0.0.1 .1.3.6.1.4.1.8072.2

PCAP-SNMP-MONITOR-MIB DEFINITIONS ::= BEGIN

IMPORTS
	netSnmpExamples		              FROM NET-SNMP-EXAMPLES-MIB
	OBJECT-TYPE, Integer32, Counter64, TimeTicks
	MODULE-IDENTITY                       FROM SNMPv2-SMI
	DisplayString                         FROM SNMPv2-TC
	MODULE-COMPLIANCE, OBJECT-GROUP       FROM SNMPv2-CONF;

--
-- A brief description and update information about this mib.
--
pcapSnmpMonitorMIB MODULE-IDENTITY
    LAST-UPDATED "201103151500Z"
    ORGANIZATION "some.random.org"
    CONTACT-INFO "email: root@localhost"
    DESCRIPTION  "Packet capture statistics"
    ::= { netSnmpExamples 3000 }

-- Define typical mib nodes, like where the objects are going to lie.
netMIBObjects     OBJECT IDENTIFIER ::= { pcapSnmpMonitorMIB 1 }
netMIBTables      OBJECT IDENTIFIER ::= { pcapSnmpMonitorMIB 2 }

netAgentUptime OBJECT-TYPE
	SYNTAX		TimeTicks
	MAX-ACCESS	read-only
	STATUS		current
	DESCRIPTION	"Count of seconds that daemon has been executing for."
	DEFVAL		{ 0 }
	::= { netMIBObjects 1 }

fltCount OBJECT-TYPE
	SYNTAX		Integer32
	MAX-ACCESS	read-only
	STATUS		current
	DESCRIPTION	"Count of filter entries."
	DEFVAL		{ 0 }
	::= { netMIBObjects 2 }

pcapFilterTable OBJECT-TYPE
	SYNTAX		SEQUENCE OF pcapFilterEntry
	MAX-ACCESS	not-accessible
	STATUS		current
	DESCRIPTION	"A table of pcap filters."
	::= { netMIBTables 1 }

pcapFilterEntry OBJECT-TYPE
	SYNTAX		PcapFilterEntry
	MAX-ACCESS	not-accessible
	STATUS		current
	DESCRIPTION	"Contains info about each pcap filter."
	::= { pcapFilterTable 1 }

PcapFilterEntry ::= SEQUENCE {
	fltIndex	INTEGER,
	ifDescr		DisplayString,
	fltDescr	DisplayString,
	fltBPF		DisplayString,
	fltPackets	Counter64,
	fltBytes	Counter64
}

fltIndex OBJECT-TYPE
	SYNTAX		INTEGER (1..2147483647)
	MAX-ACCESS	not-accessible
	STATUS		current
	DESCRIPTION	"A unique value, greater than zero, for each filter."
	::= { pcapFilterEntry 1 }

ifDescr OBJECT-TYPE
	SYNTAX		DisplayString (SIZE (0..255))
	MAX-ACCESS	read-only
	STATUS		current
	DESCRIPTION	"A textual string naming the interface."
	::= { pcapFilterEntry 2 }

fltDescr OBJECT-TYPE
	SYNTAX		DisplayString (SIZE (0..255))
	MAX-ACCESS	read-only
	STATUS		current
	DESCRIPTION	"A textual string naming the PCAP filter."
	::= { pcapFilterEntry 3 }

fltBPF OBJECT-TYPE
	SYNTAX		DisplayString (SIZE (0..8191))
	MAX-ACCESS	read-only
	STATUS		current
	DESCRIPTION	"A textual string of the BPF / PCAP expression for this filter."
	::= { pcapFilterEntry 4 }

fltPackets OBJECT-TYPE
	SYNTAX		Counter64
	MAX-ACCESS	read-only
	STATUS		current
	DESCRIPTION	"Count of packets that have matched this filter."
	::= { pcapFilterEntry 5 }

fltBytes OBJECT-TYPE
	SYNTAX		Counter64
	MAX-ACCESS	read-only
	STATUS		current
	DESCRIPTION	"Count of bytes that have matched this filter."
	::= { pcapFilterEntry 6 }

END
